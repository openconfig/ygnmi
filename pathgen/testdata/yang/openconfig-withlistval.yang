module openconfig-withlistval {
  namespace "urn:ocwithlistval";
  prefix "oc";

  import openconfig-extensions { prefix oc-ext; }

  description
    "A simple test module that is used to verify code generation for a
    schema that contains lists";

  typedef ieeefloat32 {
    type binary {
      length "4";
    }
    description
      "An IEEE 32-bit floating point number. The format of this number
      is of the form:
        1-bit  sign
        8-bit  exponent
        23-bit fraction
      The floating point value is calculated using:
        (-1)**S * 2**(Exponent-127) * (1+Fraction)";
  }

  grouping single-key-config {
    leaf key { type string; }
    leaf value { type int64; }
  }

  grouping multi-key-config {
    leaf key1 { type uint32; }
    leaf key2 { type uint64; }
  }

  grouping lists-top {
    container model {
      container a {
        list single-key {
          key "key";

          leaf key {
            type leafref {
              path "../config/key";
            }
          }

          container config {
            uses single-key-config;
          }

          container state {
            config false;
            uses single-key-config;
            leaf counter {
              type ieeefloat32;
            }
            leaf-list counters {
              type ieeefloat32;
            }
          }

          container nested-lists {
            list nested-list {
              key "key";
              leaf key {
                type leafref {
                  path "../config/key";
                }
              }
              container config {
                  uses single-key-config;
              }
              container state {
                config false;
                uses single-key-config;
              }
            }
          }

          container ordered-lists {
            list ordered-list {
              key "key";
              ordered-by user;

              leaf key {
                type leafref {
                  path "../config/key";
                }
              }

              container config {
                uses single-key-config;
              }

              container state {
                config false;
                uses single-key-config;
              }
            }
          }

          container inner-a {
            oc-ext:telemetry-atomic;
            list single-key {
              key "key";

              leaf key {
                type leafref {
                  path "../config/key";
                }
              }

              container config {
                uses single-key-config;
              }

              container state {
                config false;
                uses single-key-config;
              }
            }
          }
        }
      }

      container b {
        list multi-key {
          key "key1

                key2"; // Test for irregular spacing

          leaf key1 {
            type leafref {
              path "../config/key1";
            }
          }

          leaf key2 {
            type leafref {
              path "../config/key2";
            }
          }

          container config {
            uses multi-key-config;
          }

          container state {
            config false;
            uses multi-key-config;
          }
        }
      }

      container c {
        config false;
        list no-key {
          container foo {
            container state {
              config false;
              uses single-key-config;
            }
          }
        }
      }
    }
  }

  uses lists-top;

}
